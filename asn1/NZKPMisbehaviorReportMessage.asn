MisbehaviorReportNZKP {
    itu-t(0) identified-organization(4) nzkpmr(0) etsi(0) itsDomain(5) wg5(5) en (302637) tr(103460) ts (103097) version(1)
}

DEFINITIONS AUTOMATIC TAGS ::=

BEGIN

IMPORTS
Version, StationID, MisbehaviorReport
FROM
EtsiTr103460MisbehaviorReportMessage { 
itu-t(0) identified-organization(4) etsi(0) itsDomain(5) wg5(5) en (302637) tr(103460) ts (103097) mrm(0) version(1)
}

EtsiTr103460MisbehaviorReportMessage, AuthorizationTicket
FROM
ITS-Container {
itu-t (0) identified-organization (4) etsi (0) itsDomain (5)
wg1 (1) ts (102894) cdd (2) version (2)
};

MessageID ::= INTEGER(0..4294967295)

MisbehaviorReportNZKP::= SEQUENCE {
    header Header,
    payload Payload
}

Header ::= SEQUENCE {
    version Version,
    messageID MessageID,
    stationID StationID
}

Payload ::= SEQUENCE {
   -- misbehaviorReport MisbehaviorReport,
    --authorizationTicket AuthorizationTicket,
    nzkps NZKPS
  --  sizes SIZES
}

--SIZES ::= SEQUENCE OF INTEGER

NZKPS ::= SEQUENCE OF OCTET STRING

--NZKP ::= SEQUENCE {
--    committedValue OCTET STRING,
--    proof OCTET STRING
--}

--CommittedValues ::= SET OF CommittedValue

--CommittedValue ::= BIT STRING

END
